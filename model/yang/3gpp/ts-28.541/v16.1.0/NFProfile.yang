submodule NFProfile {
 
	belongs-to ngc { prefix ngc; }
	
    import nrm-types-3gpp { prefix nrm-type; revision-date "2018-07-31"; }
    import ietf-inet-types { prefix inet; revision-date "2010-09-24"; }

    revision 2018-08-08 {
        description "Initial revision";
    }
    

    grouping UdrInfo {
    	leaf groupId {
    		type string;
    	}
    	
    	list supiRange {
    		key "start end pattern";
    		uses nrm-type:SupiRange;
    	}
    	
    	
    	list gpsiRange {
       		key "start end pattern";
    		uses nrm-type:IdentityRange;
    	}
    	
    	list externalGroupIdentifiersRange {
       		key "start end pattern";
    		uses nrm-type:IdentityRange;
    	}
    	
    	leaf-list supportedDataSet {
    		type nrm-type:DataSetId; 
    	}

    }
    
    grouping UdmInfo {
    	leaf groupId {
    		type string;
    	}
    	
    	list supiRange {
      		key "start end pattern";
    		uses nrm-type:SupiRange;
    	}
    	
    	
    	list gpsiRange {
      		key "start end pattern";
    		uses nrm-type:IdentityRange;
    	}
    	
    	list externalGroupIdentifiersRange {
      		key "start end pattern";
   		    uses nrm-type:IdentityRange;
    	}
    	
		leaf routingIndicator {
			type string;
		}
    }
    
    grouping AusfInfo {
    	leaf groupId {
    		type string;
    	}
    	
    	list supiRange {
      		key "start end pattern";
    		uses nrm-type:SupiRange;
    	}
    	
		leaf routingIndicator {
			type string;
		}
   }
    
    grouping AmfInfo {
    	leaf amfRegionId {
    		type string;
    	}
    	
    	leaf amfSetId {
    		type string;
    	}
    	
	    list guami {
	    	//FFS to use embedded identifier
	    	key k_id;
	    	leaf k_id {
	    		type string;
	    	}
	    	uses nrm-type:Guami;
	    }
	    
	    list tai {
	    	//FFS to use embedded identifier
	    	key k_id;
	    	leaf k_id {
	    		type string;
	    	}
	    	uses nrm-type:Tai;
	    }
	
	    list backupInfoAmfFailure {
	    	//FFS to use embedded identifier
	    	key k_id;
	    	leaf k_id {
	    		type string;
	    	}
	    	uses nrm-type:Guami;
	    }
	    
	    list backupInfoAmfRemoval {
	    	//FFS to use embedded identifier
	    	key k_id;
	    	leaf k_id {
	    		type string;
	    	}
	    	uses nrm-type:Guami;
	    }
    
    }
    
    grouping SmfInfo {
    	leaf-list dnn {
    		type nrm-type:t_Dnn;
    	}
    	
	    list tai {
	    	//FFS to use embedded identifier
	    	key k_id;
	    	leaf k_id {
	    		type string;
	    	}
	    	uses nrm-type:Tai;
	    }
    	
    	leaf pgwFqdn {
    		type inet:domain-name;
    	}
    }
    
    grouping UpfInfo {
    	list sNssaiUpfInfo {
    		key sNssai;
    		uses nrm-type:SnssaiUpfInfoItem;
    	}
    	
    	leaf smfServingArea {
    		type string;
    	}
    	
    	list interfaceUpfInfo {
	    	//FFS to use "choiced" identifier
	    	key k_id;
	    	leaf k_id {
	    		type string;
	    	}
   		    //key "interfaceType address";
    		uses nrm-type:InterfaceUpfInfoItem;
    	}
    }
    
    grouping PcfInfo {
    	leaf-list dnn {
    		type nrm-type:t_Dnn;
    	}
    }
    
    grouping BsfInfo {
    	list ipv4AddressRange {
    		key "start end"; 
    		uses nrm-type:Ipv4AddressRange;
    	}
    	list ipv6PrefixRange {
    		key "start end";
    		uses nrm-type:Ipv6PrefixRange;
    	}
    }
    

    grouping NFService {
    	
    	leaf serviceInstanceID {
            description "";
    		mandatory "true";
    		type string;
    	}
    	
    	leaf serviceName {
    		mandatory "true";
    		type string;   		
    	}
    	
    	container version { uses nrm-type:NFServiceVersion; }
    	
    	leaf schema {
    		mandatory "true";
    		type string;     		
    	}
    	
	    leaf fqdn {
	    	type inet:domain-name;
	    }
	
	    leaf interPlmnFqdn {
	    	type inet:domain-name;
	    }
	
     	list ipEndPoint {
	    	//FFS to use "choiced" identifier
	    	key k_id;
	    	leaf k_id {
	    		type string;
	    	}
//     		key "address port";
     		uses nrm-type:ipEndPoint;
     	}
     	
    	leaf apiPrefix {
    		type string;
    	}
    	
    	list defaultNotificationSubscription {
    		key notificationType;
    		uses nrm-type:defaultNotificationSubscription;
    	}

    	list allowedPlmn {
    		key "MCC MNC";
    		uses nrm-type:pLMNId;
    	}
    	
    	leaf-list allowedNfType {
    		type nrm-type:NFType;
    	}
    	
    	leaf-list allowedDomain {
    		type string;
    	}
    	
    	leaf-list allowedNssais {
	    	type nrm-type:t_s-NSSAI;    		
    	}
    	
    	leaf capacity {
	         type uint8;    		
    	}
    	
    	leaf load {
	    	type nrm-type:t_Load;
    	}
    	
    	leaf supportedFeatures {
    		type nrm-type:SupportedFeatures;
    	}
    	
    }
        
    grouping NFProfile {
    	
	    leaf nfInstanceId {
	       	mandatory "true";
	    	type string;
	    }
	    
	    leaf nfType {
	    	mandatory "true";
	    	type nrm-type:NFType;
	    }
	           
	    leaf nfStatus {
	       	mandatory "true";
	       	type nrm-type:NFStatus;
	    }
	
	    container plmn {
	    	uses nrm-type:pLMNId;
	    }
	           
	    leaf-list sNssais {
	    	type nrm-type:t_s-NSSAI;
	    }
	
	    leaf-list nsi {
	    	type string;
	    }
	    
	    leaf fqdn {
	    	type inet:domain-name;
	    }
	
	    leaf interPlmnFqdn {
	    	type inet:domain-name;
	    }
	    
	    leaf-list ipv4Address {
	    	type inet:ipv4-address;
	    }
	 
	    leaf-list ipv6Address {
	    	type inet:ipv6-address;
	    }
	    
	    leaf-list ipv6Prefix {
	    	type inet:ipv6-prefix;
	    }
	    
	    leaf capacity {
	         type uint8;
	    }
	    
	    leaf load {
	    	type nrm-type:t_Load;
	    }
	
	    leaf locality {
	            type string;
	    }
	    
	    leaf priority {
	        type uint8;
	    }

	    container udrInfo { uses UdrInfo; }
	    container udmInfo { uses UdmInfo; }
	    container ausfInfo { uses AusfInfo; }
	    container amfInfo { uses AmfInfo; }
	    container smfInfo { uses SmfInfo; }
		container upfInfo { uses UpfInfo; }
		container pcfInfo { uses PcfInfo; }
		container bsfInfo { uses BsfInfo; }

        list nfService {
            min-elements "0";
            description "";
        	key serviceInstanceID;
        	uses NFService;
        }

    }

}

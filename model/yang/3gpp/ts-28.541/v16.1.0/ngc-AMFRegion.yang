submodule ngc-AMFRegion {
    
	belongs-to ngc { prefix ngc; }
    
    import ManagedFunction { prefix mf; revision-date "2018-07-31"; }
    import nrm-types-3gpp { prefix nrm-type; revision-date "2018-07-31"; }
    import ietf-inet-types { prefix inet; revision-date "2010-09-24"; }  

    revision 2018-12-18 {
        description "initial verison";
    }

    grouping AMFRegion {
        uses mf:ManagedFunction; 
        
		list pLMNId {
            min-elements "1";
            description "a list of PLMN-Id, PLMN-Id= Mobile Country Codes (MCC)|| Mobile Network Codes(MNC) ";
            config "true";
            key "MCC MNC";
            uses nrm-type:pLMNId;
        }
    		
        leaf aMFRegionId {
            config "true";
            description "";
            type nrm-type:t_aMF-Region-id;
        }
        
        leaf-list tAC {
            min-elements "1";
            config "false";
        	type nrm-type:t_tAC; 
       	
        }
                
        leaf-list s-NSSAI {
            min-elements "0";
            config "true";
            description "It represents the list of S-NSSAI the managed object is capable
                    of supporting, an S-NSSAI is comprised of a SST (Slice/Service
                    type) and an optional SD (Slice Differentiator) field, (Ref. 3GPP
                    TS 23.003 [13]). ";
            reference "3GPP TS 23.003";
        	type nrm-type:t_s-NSSAI; 
        }
        
        leaf-list aMFSet {
            description "AMF Set list in the aMFRegion";
        	min-elements "0";
            config "true";
        	type nrm-type:t_dn;    	
        }
        
     }

}

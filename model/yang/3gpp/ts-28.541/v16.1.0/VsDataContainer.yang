module VsDataContainer {
    namespace "urn:3gpp:tsg:sa5:nrm::VsDataContainer";
    prefix "vsData";
    import Top { prefix top; revision-date "2018-07-31"; }
    import nrm-types-3gpp { prefix nrm-type; revision-date "2018-07-31"; }

    revision 2018-12-18 {
        description "Initial revision";
    }
    grouping VsDataContainer {
       	uses top:Top;
		leaf id {
            mandatory "true";
            config "false";
            description "derived from top_";
            type nrm-type:t_dn;
        }
        leaf vsDataType {
              mandatory "true";
              config "true";
              description "";
              type string;
          }
        leaf vsDataFormatVersion {
              mandatory "true";
              config "false";
              description "";
              type string;
          }
        anydata vsData;
        list vsDataContainer {
            min-elements "0";
        	uses VsDataContainer;
        }

      }
}

submodule ngran-nRCellDU {
    
	belongs-to ngran { prefix ngran; }
    
    import ManagedFunction { prefix mf; revision-date "2018-07-31"; }
    import nrm-types-3gpp { prefix nrm-type; revision-date "2018-07-31"; }

    description "NRCellDU derived from basic ManagedFunction";

    revision 2018-08-02 {
        description "Initial revision";
    }

    grouping NRCellDU {
        uses mf:ManagedFunction;
        
        leaf nCI {        	
            config "true";
            description "It uniquely identifies a NR cell within a PLMN."; 
            reference "See NR Cell identifier (NCI) subclause 8.2 of 3GPP TS 38.300 [3].";
       	    type nrm-type:t_NCI;        	
        }

		list pLMNId {
            min-elements "1";
            description "a list of PLMN-Id, PLMN-Id= Mobile Country Codes (MCC)|| Mobile Network Codes(MNC) ";
            config "true";
            key MCC;
            uses nrm-type:pLMNId;
        }
		
       leaf-list s-NSSAI {
            min-elements "0";
            config "true";
        	type nrm-type:t_s-NSSAI; 
       }
         
       leaf operationalState  {
            config "false";
            description "CM, It indicates the operational state of the NRCellDU instance. It describes whether the resource is installed and partially or fully operable (Enabled) or the resource is not installed or not operable (Disabled).";
            type nrm-type:t_operationalState;
        }
        leaf administrativeState  {
            description "CM, It indicates the administrative state of the NRCellDU. It describes the permission to use or prohibition against using the cell, imposed through the OAM services.";
            config "true";
            type nrm-type:t_administrativeState;
        }
       
        leaf cellState  {
            description "It indicates the usage state of the NRCellDU instance. It describes whether the cell is not currently in use (Idle), or currently in use but not configured to carry traffic (Inactive) or is currently in use and is configured to carry traffic (Active)";
        	  mandatory "true";
            config "false";
            type nrm-type:t_cellState;
        }
        leaf nRPCI {
            description "";
            mandatory "true";
            config "true";
            type nrm-type:t_nRPCI;
        }
        leaf nRTAC {
            mandatory "true";
            config "true";
            type nrm-type:t_tAC;
        }
        leaf arfcnDL {
            mandatory "true";
            config "true";
            type uint32;
        }
        leaf arfcnUL {
            config "true";
            type uint32;
        }
        leaf arfcnSUL {
            config "true";
            type uint32;
        }
        leaf bSChannelBwDL {
            mandatory "true";
            config "true";
            type uint32;
        }
        leaf bSChannelBwUL {
            config "true";
            type uint32;
        }
        leaf bSChannelBwSUL {
            config "true";
            type uint32;
        }
       
        //refer to nRSectorCarrier
        leaf-list NRSectorCarrier {
            min-elements "0";
            description "";
            config "true";
            type nrm-type:t_dn;    	       	
        }
        //refer to bwp
        leaf-list bWP {
            min-elements "0";
            description "";
            config "true";
            type nrm-type:t_dn;    	       	
        }
     }
}

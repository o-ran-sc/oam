submodule ngran-nRSectorCarrier {
    
	belongs-to ngran { prefix ngran; }
    
    import nrm-types-3gpp { prefix nrm-type; revision-date "2018-07-31"; }
    import ManagedFunction { prefix mf; revision-date "2018-07-31"; }

    description "NRSectorCarrier";

    revision 2018-08-02 {
        description "Initial revision";
    }

    grouping NRSectorCarrier {
        description "";
        uses mf:ManagedFunction;

        leaf txDirection {
            mandatory "true";
            config "true";
            type nrm-type:TxDirection;
       }
        leaf configuredMaxTxPower {
            mandatory "true";
            config "false";
            description "";
            type uint16;
        }
        leaf arfcnDL {
            config "true";
            type uint32;
        }
        leaf arfcnUL {
            config "true";
            type uint32;
        }
        leaf bSChannelBwDL {
            config "true";
            type uint32;
        }
        leaf bSChannelBwUL {
            config "true";
            type uint32;
        }
        leaf sectorEquipmentFunction {
            mandatory "true";
            config "true";
            description "fqBand for NR should be defined";
            reference "23.622";
            type nrm-type:t_dn;       	
        }		
     }    
}

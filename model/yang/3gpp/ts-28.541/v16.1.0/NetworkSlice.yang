module NetworkSlice {
    namespace "urn:3gpp:tsg:sa5:nrm:NetworkSlice";
    prefix "ns";
    
    import SubNetwork { prefix subnet; revision-date "2018-07-31"; }
    import nrm-types-3gpp { prefix nrm-type; revision-date "2018-07-31"; }
    include ServiceProfile;
    
    
    description "";
    

    revision 2018-08-09 {
        description "Initial revision";
    }
    
    container NetworkSlice {
    	uses subnet:SubNetwork;
    	
        leaf nSSIId {
            mandatory "true";
            config "false";
            description "";
            type nrm-type:t_dn;
        }
    	
        leaf operationalState {
            mandatory "true";
            config "false";
            description "";
            type nrm-type:t_operationalState;
        }
    	
        leaf administrativeState {
            mandatory "true";
            config "true";
            description "";
            type nrm-type:t_administrativeState;
        }
    	
        list serviceProfile {
                min-elements "1";
                config "true";
                description "";
                key serviceProfileId;
                uses ServiceProfile;
            }
    	
    	
    }

}

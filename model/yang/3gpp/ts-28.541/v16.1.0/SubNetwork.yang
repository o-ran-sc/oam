module SubNetwork {
    namespace "urn:3gpp:tsg:sa5:nrm:SubNetwork";
    prefix "subnet";
    import nrm-types-3gpp { prefix nrm-type; revision-date "2018-07-31"; }
    import Top { prefix top; revision-date "2018-07-31"; }
import VsDataContainer {prefix vsData; revision-date "2018-12-18"; }
organization "3gpp SA5";
    description "define basic SubNetwork which will be augmented by other IOCs";

    revision 2018-07-31 {
        description "Initial revision";
    }
        
    grouping SubNetwork {
       	uses top:Top;
		leaf id {
            mandatory "true";
            config "false";
            description "derived from top_";
            type nrm-type:t_dn;
        }
        leaf dnPrefix {
            mandatory "true";
            config "false";
            description "derived from domain_";
            type string;
        }
        
        leaf userLabel {
            description "derived from domain_";
            mandatory "true";
            config "true";
            type string;
        }
        leaf userDefinedNetworkType {
            description "derived from domain_";
            mandatory "true";
            config "true";
            type string;
        	
        }
        leaf-list setOfMcc {
            min-elements "0";
            description "";
        	
            config "false";
            type nrm-type:t_mcc;

        }
        list vsDataContainer {
            min-elements "0";
       	    uses vsData:VsDataContainer;
        }
    }
    	

    container SubNetwork {
    	uses SubNetwork;
    }
}

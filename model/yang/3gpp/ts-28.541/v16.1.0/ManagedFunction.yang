module ManagedFunction {
    namespace "urn:3gpp:tsg:sa5:nrm:ManagedFunction";
    prefix "mf";
    import Top { prefix top; revision-date "2018-07-31"; }
    import nrm-types-3gpp { prefix nrm-type; revision-date "2018-07-31"; }
import VsDataContainer {prefix vsData; revision-date "2018-12-18"; }
    description "common/basic MF class to be inherited/reused by other child MF classes ";

    revision 2018-07-31 {
        description "Initial revision";
    }

    grouping  ManagedFunction {
    	description "";
    	
    	uses top:Top;
    	  leaf id {
            description "";
            mandatory "true";
            config "false";
            type nrm-type:t_dn;
        }
        leaf userLabel {
            mandatory "false";
            config "true";
            type string;
        }
        container vnfParametersList {
            description "It shall be supported if the MF instance is realized by one or more VNF instance(s). Otherwise this attribute shall be absent ";
            leaf vnfInstanceId {
                mandatory "true";
                type string;
            }
            leaf vnfdId  {
                type string;
            }
            leaf flavourId  {
                description "Identifier of the VNF Deployment Flavour applied to this VNF instance";
                reference "clause 9.4.3 of ETSI GS NFV-IFA 008 ";
                type string;
            }
            leaf autoScalable {
                description "Indicator of whether the auto-scaling of this VNF instance is enabled or disabled. The type is Boolean";
                type boolean;
            }
        }
        container peeParametersList {
           description "It shall be supported if the control and monitoring of PEE parameters is supported by the ManagedFunction or sub-class instance.";       
           leaf siteIdentification {
                mandatory "true";
                description "The identification of the site where the ManagedFunction resides.";
                type string;
            }
            leaf siteLatitude  {
                description "The latitude of the site where the ManagedFunction instance resides, based on World Geodetic System (1984 version) global referenceframe (WGS 84). Positive values correspond to the northern hemisphere. This attribute is optional in case of BTSFunction and RNCFunction  instance(s). allowedValues: -90.0000 to +90.0000 ";
                when "contains(../../objectClass,'BTSFunction') or contains(../../objectClass,'RNCFunction')";
                type decimal64 {
                	fraction-digits 4;
                	range "-90.0000 .. 90.0000";
                }
            }
            leaf siteLongitude {
                description "The longitude of the site where the ManagedFunction instance resides, based on World Geodetic System (1984 version) global reference frame (WGS 84). Positive values correspond to degrees east of 0 degrees longitude. This attribute is optional in case of BTSFunction and RNCFunction instance(s). allowedValues: -180.0000to +180.0000 ";
                when "contains(../../objectClass,'BTSFunction') or contains(../../objectClass,'RNCFunction')";
                type decimal64 {
                	fraction-digits 4;
                	range "-180.0000 .. 180.0000";
                }
            }
            leaf siteDescription {
                mandatory "true";
                description "An operator defined description of the site where the ManagedFunction instance resides.";
                type string;
            }
            leaf equipmentType {
                mandatory "true";
                description "The type of equipment where the managedFunction instance resides. allowedValues: see clause 4.4.1 of ETSI ES 202 336-12 [18]. ";
                 type enumeration {
                	enum RRU;
                	enum BBU;
                	enum Wide-area-BS-cabinet;
                	enum Medium-range-BS;
                 }
            }
            leaf environmentType {
                mandatory "true";
                description "The type of environment where the managedFunction instance resides. allowedValues: see clause 4.4.1 of ETSI ES 202 336-12 [18]. ";
                type enumeration {
               	enum Indoor;
               	enum Outdoor;
                }
            }
            leaf powerInterface {
                mandatory "true";
                description "The type of power. allowedValues: see clause 4.4.1 of ETSI ES202 336-12 [18]. ";
                type enumeration {
               	enum AC;
               	enum DC;
                }
            }
        }
        list vsDataContainer {
            min-elements "0";
       	    uses vsData:VsDataContainer;
        }
    }
}

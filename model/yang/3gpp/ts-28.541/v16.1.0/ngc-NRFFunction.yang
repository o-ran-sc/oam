submodule ngc-NRFFunction {
    
	belongs-to ngc { prefix ngc; }
    
	import EP_RP { prefix ep-rp; revision-date "2018-07-31"; }
    import ManagedFunction { prefix mf; revision-date "2018-07-31"; }
    import nrm-types-3gpp { prefix nrm-type; revision-date "2018-07-31"; }
    import ietf-inet-types { prefix inet; revision-date "2010-09-24"; }
    include NFProfile; 

    description "NRFFunction derived from basic ManagedFunction";

    revision 2018-08-07 {
        description "Initial revision";
    }

    grouping NRFFunction {
        uses mf:ManagedFunction; 
        
		list pLMNId {
            min-elements "1";
            description "a list of PLMN-Id, PLMN-Id= Mobile Country Codes (MCC)|| Mobile Network Codes(MNC) ";
            config "true";
            key "MCC MNC";
            uses nrm-type:pLMNId;
        }
    		
        leaf sBIFQDN {
            mandatory "true";
            config "true";
            description " ";
            type inet:domain-name;
        }
        
        leaf-list sBIService {
            description ""; 
            min-elements "1";
            config "false";
        	type string; 
       	
        }
    		
        leaf-list s-NSSAI {
            min-elements "0";
            config "true";
            description "It represents the list of S-NSSAI the managed object is capable
                    of supporting, an S-NSSAI is comprised of a SST (Slice/Service
                    type) and an optional SD (Slice Differentiator) field, (Ref. 3GPP
                    TS 23.003 [13]). ";
            reference "3GPP TS 23.003";
        	type nrm-type:t_s-NSSAI; 
        }
		
        list nFProfile {
            description "CM only required when NF profile is registered and deregistered by management system.";
            min-elements "1";
            config "true";
            key nfInstanceId;
        	uses NFProfile; 
       	
        }
    		
        leaf-list nSIId {
            description "Is it really needed if network slicing feature enabled Seems it's only required for NSSF";
            min-elements "1";
            config "false";
        	type nrm-type:t_NsiId; 
       	
        }
    		
        
     	list EP_N27 { uses ep-rp:EP_N26; }
    	list EP_SBI_X {
    		key id;
            uses ep-rp:EP_SBI_X;
    	}
    	
     }

}

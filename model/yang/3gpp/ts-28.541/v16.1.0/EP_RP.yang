module EP_RP {
    namespace "urn:3gpp:tsg:sa5:nrm:EP_RP";
    prefix "ep-rp";

    import Top { prefix top; revision-date "2018-07-31"; }
    import nrm-types-3gpp { prefix nrm-type; revision-date "2018-07-31"; }
    import ietf-inet-types { prefix inet; revision-date "2010-09-24"; }
import VsDataContainer {prefix vsData; revision-date "2018-12-18"; }
    description "common/basic MF class to be inherited/reused by other child MF classes ";

    revision 2018-07-31 {
        description "Initial revision";
    }

    grouping local-address {
        leaf ip_address {
        	type inet:ip-address;   
        }
        leaf vlan_id {
           	type uint16;
        }	
    }
    
    grouping EP_RP {
        description "";
    	uses top:Top;
        leaf id {
            description "";
            mandatory "true";
            type nrm-type:t_dn;
        }
        leaf userLabel {
            description "";
            mandatory "false";
            type string;
        }
        leaf farEndEntity {
            mandatory "false";
            type nrm-type:t_dn;
        }
        list vsDataContainer {
            min-elements "0";
       	    uses vsData:VsDataContainer;
        }
    }
    
    grouping EP_XX {
        description "as all EPs defined in NGRAN and 5GC have same attributes, define a common EP for all endpoints for reusing";
    	uses EP_RP;
        container localAddress  {
            presence "true";
            description "";
        	uses local-address;
        }
        leaf remoteAddress  {
            description "";
            mandatory "false";
        	type inet:ip-address;
        }        	
    }
    
    grouping EP_E1 {
        description "";
    	uses EP_XX;
   }
  
    grouping EP_F1C {
        description "";
    	uses EP_XX;
   }

    grouping EP_F1U {
        description "";
    	uses EP_XX;
   }
    
    grouping EP_XnC {
        description "";
    	uses EP_XX;
   }
  
    grouping EP_XnU {
        description "";
    	uses EP_XX;
   }
  
    grouping EP_NgC {
        description "";
    	uses EP_XX;
   }
  
    grouping EP_NgU {
        description "";
    	uses EP_XX;
   }
  
    grouping EP_X2C {
        description "";
    	uses EP_XX;
   }
  
    grouping EP_X2U {
        description "";
    	uses EP_XX;
   }
  
    grouping EP_S1U {
        description "";
    	uses EP_XX;
   }
  
    grouping EP_N2 {
        description "";
    	uses EP_XX;
   }
  
    grouping EP_N3 {
        description "";
    	uses EP_XX;
   }
  
    grouping EP_N4 {
        description "";
    	uses EP_XX;
   }
  
    grouping EP_N5 {
        description "";
    	uses EP_XX;
   }
  
    grouping EP_N6 {
        description "";
    	uses EP_XX;
   }
  
    grouping EP_N7 {
        description "";
    	uses EP_XX;
   }
  
    grouping EP_N8 {
        description "";
    	uses EP_XX;
   }
  
    grouping EP_N9 {
        description "";
    	uses EP_XX;
   }
  
    grouping EP_N10 {
        description "";
    	uses EP_XX;
   }
  
    grouping EP_N11 {
        description "";
    	uses EP_XX;
   }
  
    grouping EP_N12 {
        description "";
    	uses EP_XX;
   }
  
    grouping EP_N13 {
        description "";
    	uses EP_XX;
   }
  
    grouping EP_N14 {
        description "";
    	uses EP_XX;
   }
  
    grouping EP_N15 {
        description "";
    	uses EP_XX;
   }
  
    grouping EP_N16 {
        description "";
    	uses EP_XX;
   }
  
    grouping EP_N17 {
        description "";
    	uses EP_XX;
   }
  
    grouping EP_N20 {
        description "";
    	uses EP_XX;
   }
  
    grouping EP_N21 {
        description "";
    	uses EP_XX;
   }
  
    grouping EP_N22 {
        description "";
    	uses EP_XX;
   }
  
    grouping EP_N26 {
        description "";
    	uses EP_XX;
   }
  
    grouping EP_S5C {
        description "";
    	uses EP_XX;
   }
  
    grouping EP_S5U {
        description "";
    	uses EP_XX;
   }
  
    grouping EP_Rx {
        description "";
    	uses EP_XX;
   }
  
    grouping EP_MAP_SMSC {
        description "";
    	uses EP_XX;
   }
  
    grouping EP_NLS {
        description "";
    	uses EP_XX;
   }
  
    grouping EP_NLG {
        description "";
    	uses EP_XX;
   }
  
    grouping EP_N27 {
        description "";
    	uses EP_XX;
   }
  
    grouping EP_N31 {
        description "";
    	uses EP_XX;
   }
  
    grouping EP_N32 {
        description "";
    	uses EP_XX;
   }
  
    grouping EP_SBI_X {
        description "It's used for the services consumed by the contol plane function. Far entity and remoteAdress are requied for this endpoint";
    	uses EP_XX;
        leaf-list sBIService {
            min-elements "1";
            config "false";
        	type string;      	
        }    		
   }
  
    grouping EP_SBI_IPX {
        description "It's used for the SEPP services consumed by the contol plane function. Far entity and remoteAdress are requied for this endpoint";
    	uses EP_XX;
        leaf-list sBIService {
            min-elements "1";
            config "false";
        	type string;      	
        }    		
   }
  
   grouping sAP {
   		leaf dn {
   			type inet:domain-name;   			
   		}
   		leaf port {
   			type uint16;
   		}  
   }
   
   grouping EP_NBI_X {
        description "The service access point of the control plane function. It's used for the services (including SEPP service) provided by the contol plane function. Far entity and remoteAdress are uncessary for this endpoint ";
    	uses EP_RP;
        container localSAP  {
            presence "true";
            description "";
        	uses sAP;
        }
        leaf-list sBIService {
            min-elements "1";
            config "false";
        	type string;      	
        }         	
    }    
}

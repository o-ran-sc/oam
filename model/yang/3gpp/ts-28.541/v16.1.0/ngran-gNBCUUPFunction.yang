submodule ngran-gNBCUUPFunction {
    
	belongs-to ngran { prefix ngran; }
    
	import EP_RP { prefix ep-rp; revision-date "2018-07-31"; }
    import ManagedFunction { prefix mf; revision-date "2018-07-31"; }
    import nrm-types-3gpp { prefix nrm-type; revision-date "2018-07-31"; }
    

    description "GNBCUUPFunction derived from basic ManagedFunction, for 3 split deployment mode only";

    revision 2018-08-02 {
        description "15.0.2";
    }

    grouping GNBCUUPFunction {
            uses mf:ManagedFunction; 

            leaf gNBId {
                description "It identifies a gNB within a PLMN. See gNB Identifier (gNB ID) of subclause 8.2 of 3GPP TS 38.300 [3]). See Global gNB ID in subclause 9.3.1.6 of 3GPP TS 38.413 [5]. ";
                mandatory "true";
                config "false";
                type uint32;
            }
           leaf gNBIdLength {
                description "It indicates the number of bits for encoding the gNB ID.";
                mandatory "true";
                config "false";
                type uint32 {
					range "22..32";
				}
            }
            
    		list pLMNId {
                description "a list of PLMN-Id, PLMN-Id= Mobile Country Codes (MCC)|| Mobile Network Codes(MNC) ";
                config "true";
                key "MCC MNC";
                uses nrm-type:pLMNId;
            }   		
        list EP_F1U { uses ep-rp:EP_F1U; }

        container EP_E1 { uses ep-rp:EP_E1; }
    		choice gNB-type {
    			case gNB {
    				list EP_NgU { uses ep-rp:EP_NgU; }
    				list EP_XnU { uses ep-rp:EP_XnU; }
    			}
    			case en-gNB {
    				list EP_X2U { uses ep-rp:EP_X2U; }
    				list EP_S1U { uses ep-rp:EP_S1U; }
    			}
    		}
     }
}

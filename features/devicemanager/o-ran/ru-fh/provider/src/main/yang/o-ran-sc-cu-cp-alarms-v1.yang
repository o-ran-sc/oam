module o-ran-sc-cu-cp-alarms-v1 {
  yang-version 1.1;
  namespace "urn:o-ran-sc:cu:cp:alarms:1.0";
  prefix osc-cu-cp-al;

  import ietf-alarms {
    prefix al;
  }

  organization
    "O-RAN Software Community";
  contact
    "www.o-ran-sc.org";
  description
    "This module defines the alarm identities for the O-RAN-SC Central Unit
     Control Plane.

     Copyright 2020 the O-RAN Software Community.

     Licensed under the Apache License, Version 2.0 (the 'License');
     you may not use this file except in compliance with the License.
     You may obtain a copy of the License at

      http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision 2020-01-18 {
    description
      "initial revision";
    reference
      "O-RAN-OAM-Interface-Specification (O1)";
  }

  identity alarm-type-id {
    base al:alarm-type-id;
    description
      "An abstract alarm type used for all O-RAN-SC specific alarm types for
       Managed Function O-CU-CP.";
  }

  identity huston-we-have-a-problem {
    base alarm-type-id;
    description
      "A generic alarm which is under development and analysis,
       must not happen in production environment.
       Instructions:
         Create an JIRA issue and provide the following intormation:
         - SMO version, build number or git hash
         - O-CU-CP version, build number or git hash
         - A procedure to reproduce the alarm.";
  }
}

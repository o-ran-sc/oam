module devicemanager-oran {

  yang-version 1;
  namespace "urn:opendaylight:params:xml:ns:yang:devicemanager-oran";
  prefix devicemanager-oran;

  organization
    "highstreet technologies GmbH";
  contact
    "Web:   <https://highstreet-technologies.com>
     O-RAN: <https://wiki.o-ran-sc.org/display/OAM/Operations+and+Maintenance";

  description
    "DeviceManager Open RAN Api Module

     Copyright 2019 highstreet technologies GmbH Intellectual Property.
     All rights reserved.

     Licensed under the Apache License, Version 2.0 (the 'License');
     you may not use this file except in compliance with the License.
     You may obtain a copy of the License at

       http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision 2019-11-15 {
    description
      "Initial revision";
    reference
      "https://jira.onap.org/browse/SDNC-877";
  }
}
